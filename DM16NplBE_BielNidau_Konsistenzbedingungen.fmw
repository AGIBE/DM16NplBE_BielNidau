FME workspace DM16NplBE_BielNidau_Konsistenzbedingungen.fmw

Parameters:
- SourceDataset_ch.ehi.fme.Main =

Readers:
- ch.ehi.fme.Main_1: ch.ehi.fme.Main from $(SourceDataset_ch.ehi.fme.Main) in EPSG:2056

ERROR: Inspector
    TACKATTRS = ERROR

Bookmark: Nicht verwendete Featureklassen
DM16NplBE_BielNidau.Nutzungsplanung.VE_FlaechenelementEinschr (reader ch.ehi.fme.Main_1)
    attributes: xtf_id xtf_char(200), Objekt xtf_char(200), Genehmigung xtf_date, Inkraftsetzung xtf_date, Beschrieb xtf_char(160), Qualitaet xtf_char(255)
DM16NplBE_BielNidau.Nutzungsplanung.GW_FlaechenelementGew (reader ch.ehi.fme.Main_1)
    attributes: xtf_id xtf_char(200), Objekt xtf_char(200), Genehmigung xtf_date, Inkraftsetzung xtf_date, Qualitaet xtf_char(255)
DM16NplBE_BielNidau.Nutzungsplanung.GW_GewaesserRV (reader ch.ehi.fme.Main_1)
    attributes: xtf_id xtf_char(200), Typ xtf_char(200), Vorschrift xtf_char(200), ArtikelNr xtf_char(40)
DM16NplBE_BielNidau.Nutzungsplanung.GW_LinienelementGew (reader ch.ehi.fme.Main_1)
    attributes: xtf_id xtf_char(200), Objekt xtf_char(200), Genehmigung xtf_date, Inkraftsetzung xtf_date, Qualitaet xtf_char(255)
DM16NplBE_BielNidau.Nutzungsplanung.VE_Vor_Einschraenkung (reader ch.ehi.fme.Main_1)
    attributes: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
DM16NplBE_BielNidau.Nutzungsplanung.VE_Vor_EinschraenkungRV (reader ch.ehi.fme.Main_1)
    attributes: xtf_id xtf_char(200), Typ xtf_char(200), Vorschrift xtf_char(200), ArtikelNr xtf_char(40)
DM16NplBE_BielNidau.Nutzungsplanung.GW_Gewaesser (reader ch.ehi.fme.Main_1)
    attributes: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
XTF_BASKETS (reader ch.ehi.fme.Main_1)
    attributes: xtf_topic xtf_char(80), xtf_id xtf_char(200), xtf_startstate xtf_char(250), xtf_endstate xtf_char(250)
XTF_DELETEOBJECT (reader ch.ehi.fme.Main_1)
    attributes: xtf_id xtf_char(200)
XTF_ERRORS (reader ch.ehi.fme.Main_1)
    attributes: message xtf_char(255), iliname xtf_char(255), tid{} xtf_char(200)
XTF_TRANSFER (reader ch.ehi.fme.Main_1)
    attributes: oidspace{}.name xtf_char(255), oidspace{}.oiddomain xtf_char(255), comment xtf_char(255)

Bookmark: Grundnutzung
DM16NplBE_BielNidau.Nutzungsplanung.GN_ZonentypRV (reader ch.ehi.fme.Main_1)
    attributes: xtf_id xtf_char(200), Typ xtf_char(200), Vorschrift xtf_char(200), ArtikelNr xtf_char(40)
    -> BulkAttributeRenamer_4
DM16NplBE_BielNidau.Nutzungsplanung.GN_Grundzone (reader ch.ehi.fme.Main_1)
    attributes: xtf_id xtf_char(200), ZonentypRef xtf_char(200), Genehmigung xtf_date, Inkraftsetzung xtf_date, Laermempfindlichkeit xtf_char(255), Beschrieb xtf_char(80), Planbeschriftung xtf_char(150), Qualitaet xtf_char(255), Bemerkung xtf_char(80), Flaechenmass xtf_int32, Verkehrsraumart xtf_char(255)
    -> BulkAttributeRenamer_5
Note: GEOM_
BulkAttributeRenamer_5
    ATTRCHOICE = All Attributes
    MODE_CHOICE = RENAME
    PATTERN_ACTION_DISP = ADDPREFIX
    REPLACE_STR = GEOM_
    -> FeatureMerger [REQUESTOR]
    -> FeatureMerger_5 [REQUESTOR]
DM16NplBE_BielNidau.Nutzungsplanung.GN_Zonentyp (reader ch.ehi.fme.Main_1)
    attributes: xtf_id xtf_char(200), Verbindlichkeit xtf_char(255), KantArt xtf_char(255), BR_Nutzungsart xtf_char(80), BR_Nutzungsmass xtf_char(80), Nutzungsziffer xtf_decimal(4,2), Nutzungsziffer_Art xtf_char(255), Gruenflaechenziffer xtf_decimal(4,2), Bemerkung xtf_char(80), Datenverwaltungsstelle xtf_char(200), ZustaendigeStelle xtf_char(200), Nutzungszone xtf_char(150), BezeichnungNZ xtf_char(300), AbkuerzungNZ xtf_char(28), DarstellungCodeNZ xtf_char(5), Bauzone xtf_char(150), BezeichnungBZ xtf_char(300), AbkuerzungBZ xtf_char(28), DarstellungCodeBZ xtf_char(5), BN_Nutzungszone xtf_char(150), BN_Bauzone xtf_char(150), BN_Spezialvorschrift xtf_char(150), BN_SV_DarstellungInNZPlan xtf_char(10), BN_SV_DarstellungInBZPlan xtf_char(10), BN_SV_DarstellungInBLPlan xtf_char(10)
    -> BulkAttributeRenamer_6
Note: TYP_
BulkAttributeRenamer_6
    ATTRCHOICE = All Attributes
    MODE_CHOICE = RENAME
    PATTERN_ACTION_DISP = ADDPREFIX
    REPLACE_STR = TYP_
    -> FeatureMerger [SUPPLIER]
    -> FeatureMerger_5 [SUPPLIER]
Note: NZ
FeatureMerger
    ATTR_ACCUM_MODE = Merge Supplier
    ATTR_CONFLICT_RES = Use Requestor
    IGNORE_NULLS = No
    JOIN_KEYS = @Value(GEOM_ZonentypRef) @Value(TYP_xtf_id) AUTO
    MERGE_TYPE = Attributes Only
    PROCESS_DUPS = NO
    REJECT_NULL_MISSING_KEYS = No
    SUPPLIERS_FIRST = No
    MERGED -> AttributeManager
AttributeManager
    ATTR_TABLE:
      SET_TO GEOM_Layer = NZ
      REMOVE TYP_Nutzungszone
      RENAME_SET_VALUE TYP_BezeichnungNZ > TYP_Bezeichnung
      RENAME_SET_VALUE TYP_AbkuerzungNZ > TYP_Abkuerzung
      RENAME_SET_VALUE TYP_DarstellungCodeNZ > TYP_DarstellungCode
      REMOVE TYP_Bauzone
      REMOVE TYP_BezeichnungBZ
      REMOVE TYP_AbkuerzungBZ
      REMOVE TYP_DarstellungCodeBZ
      REMOVE TYP_BN_Nutzungszone
      REMOVE TYP_BN_Bauzone
      REMOVE TYP_BN_Spezialvorschrift
      REMOVE TYP_BN_SV_DarstellungInBZPlan
      REMOVE TYP_BN_SV_DarstellungInBLPlan
    -> FeatureMerger_2 [REQUESTOR]
Note: BZ
FeatureMerger_5
    ATTR_ACCUM_MODE = Merge Supplier
    ATTR_CONFLICT_RES = Use Requestor
    IGNORE_NULLS = No
    JOIN_KEYS = @Value(GEOM_ZonentypRef) @Value(TYP_xtf_id) AUTO
    MERGE_TYPE = Attributes Only
    PROCESS_DUPS = NO
    REJECT_NULL_MISSING_KEYS = No
    SUPPLIERS_FIRST = No
    MERGED -> AttributeManager_2
AttributeManager_2
    ATTR_TABLE:
      SET_TO GEOM_Layer = BZ
      REMOVE GEOM_ZonentypRef
      REMOVE TYP_Nutzungszone
      REMOVE TYP_BezeichnungNZ
      REMOVE TYP_AbkuerzungNZ
      REMOVE TYP_DarstellungCodeNZ
      REMOVE TYP_Bauzone
      RENAME_SET_VALUE TYP_BezeichnungBZ > TYP_Bezeichnung
      RENAME_SET_VALUE TYP_AbkuerzungBZ > TYP_Abkuerzung
      RENAME_SET_VALUE TYP_DarstellungCodeBZ > TYP_DarstellungCode
      REMOVE TYP_BN_Nutzungszone
      REMOVE TYP_BN_Bauzone
      REMOVE TYP_BN_Spezialvorschrift
      REMOVE TYP_BN_SV_DarstellungInNZPlan
      REMOVE TYP_BN_SV_DarstellungInBZPlan
      REMOVE TYP_BN_SV_DarstellungInBLPlan
    -> FeatureMerger_2 [REQUESTOR]

Bookmark: Überlagerung
DM16NplBE_BielNidau.Nutzungsplanung.UE_FlaechenelementUeberl (reader ch.ehi.fme.Main_1)
    attributes: xtf_id xtf_char(200), Genehmigung xtf_date, Inkraftsetzung xtf_date, Objekt xtf_char(200), Beschrieb xtf_char(160), Qualitaet xtf_char(255)
    -> AttributeCreator_3
AttributeCreator_3
    ATTR_TABLE = SET_TO Layer = Überlagerung
    -> BulkAttributeRenamer
DM16NplBE_BielNidau.Nutzungsplanung.UE_UeberlagerungZone (reader ch.ehi.fme.Main_1)
    attributes: xtf_id xtf_char(200), Verbindlichkeit xtf_char(255), KantArt xtf_char(255), Art xtf_char(150), Abkuerzung xtf_char(28), Bezeichnung xtf_char(300), Planbeschriftung xtf_char(300), Nutzungsziffer xtf_decimal(4,2), Nutzungsziffer_Art xtf_char(255), Gruenflaechenziffer xtf_decimal(4,2), Bemerkung xtf_char(160), DarstellungCode xtf_char(5), Datenverwaltungsstelle xtf_char(200), ZustaendigeStelle xtf_char(200)
    -> AttributeCreator_21
AttributeCreator_21
    ATTR_TABLE = SET_TO Layer = Überlagerung
    -> BulkAttributeRenamer_2
DM16NplBE_BielNidau.Nutzungsplanung.UE_UeberlagerungZoneRV (reader ch.ehi.fme.Main_1)
    attributes: xtf_id xtf_char(200), Typ xtf_char(200), Vorschrift xtf_char(200), ArtikelNr xtf_char(40)
    -> AttributeCreator_22
AttributeCreator_22
    ATTR_TABLE = SET_TO Layer = Überlagerung
    -> BulkAttributeRenamer_4

Bookmark: Baulinien
DM16NplBE_BielNidau.Nutzungsplanung.UE_LinienelementAbstand (reader ch.ehi.fme.Main_1)
    attributes: xtf_id xtf_char(200), Objekt xtf_char(200), Beschrieb xtf_char(160), Genehmigung xtf_date, Inkraftsetzung xtf_date, Qualitaet xtf_char(255)
    -> AttributeCreator_15
AttributeCreator_15
    ATTR_TABLE = SET_TO Layer = Baulinien
    -> BulkAttributeRenamer
DM16NplBE_BielNidau.Nutzungsplanung.UE_AbstandslinieRV (reader ch.ehi.fme.Main_1)
    attributes: xtf_id xtf_char(200), Typ xtf_char(200), Vorschrift xtf_char(200), ArtikelNr xtf_char(40)
    -> AttributeCreator_24
AttributeCreator_24
    ATTR_TABLE = SET_TO Layer = Baulinien
    -> BulkAttributeRenamer_4
DM16NplBE_BielNidau.Nutzungsplanung.UE_Abstandslinie (reader ch.ehi.fme.Main_1)
    attributes: xtf_id xtf_char(200), Verbindlichkeit xtf_char(255), KantArt xtf_char(255), Art xtf_char(150), BeschrVorsprGebTeile xtf_char(255), Abkuerzung xtf_char(28), Bezeichnung xtf_char(300), Planbeschriftung xtf_char(300), Nutzungsziffer xtf_decimal(4,2), Nutzungsziffer_Art xtf_char(255), Gruenflaechenziffer xtf_decimal(4,2), Bemerkung xtf_char(160), DarstellungCode xtf_char(5), Datenverwaltungsstelle xtf_char(200), ZustaendigeStelle xtf_char(200)
    -> AttributeCreator_23
AttributeCreator_23
    ATTR_TABLE = SET_TO Layer = Baulinien
    -> BulkAttributeRenamer_2

Bookmark: Wege
DM16NplBE_BielNidau.Nutzungsplanung.WE_FlaechenelementWeg (reader ch.ehi.fme.Main_1)
    attributes: xtf_id xtf_char(200), Objekt xtf_char(200), Genehmigung xtf_date, Inkraftsetzung xtf_date, Qualitaet xtf_char(255)
    -> AttributeCreator_14
DM16NplBE_BielNidau.Nutzungsplanung.WE_LinienelementWeg (reader ch.ehi.fme.Main_1)
    attributes: xtf_id xtf_char(200), Objekt xtf_char(200), Genehmigung xtf_date, Inkraftsetzung xtf_date, Qualitaet xtf_char(255)
    -> AttributeCreator_14
AttributeCreator_14
    ATTR_TABLE = SET_TO Layer = Wege
    -> BulkAttributeRenamer
DM16NplBE_BielNidau.Nutzungsplanung.WE_WegRoute (reader ch.ehi.fme.Main_1)
    attributes: xtf_id xtf_char(200), Verbindlichkeit xtf_char(255), Art xtf_char(255), Bezeichnung xtf_char(300), Bedeutung xtf_char(255), Schutzgrad xtf_char(255), DarstellungCode xtf_char(5), Planbeschriftung xtf_char(300), Datenverwaltungsstelle xtf_char(200), ZustaendigeStelle xtf_char(200)
    -> AttributeCreator_16
AttributeCreator_16
    ATTR_TABLE = SET_TO Layer = Wege
    -> BulkAttributeRenamer_2
DM16NplBE_BielNidau.Nutzungsplanung.WE_WegRouteRV (reader ch.ehi.fme.Main_1)
    attributes: xtf_id xtf_char(200), Typ xtf_char(200), Vorschrift xtf_char(200), ArtikelNr xtf_char(40)
    -> AttributeCreator_17
AttributeCreator_17
    ATTR_TABLE = SET_TO Layer = Wege
    -> BulkAttributeRenamer_4

Bookmark: Waldgrenzen
DM16NplBE_BielNidau.Nutzungsplanung.WF_LinienelementWald (reader ch.ehi.fme.Main_1)
    attributes: xtf_id xtf_char(200), Objekt xtf_char(200), Genehmigung xtf_date, Inkraftsetzung xtf_date, Qualitaet xtf_char(255)
    -> AttributeCreator_11
AttributeCreator_11
    ATTR_TABLE = SET_TO Layer = Waldgrenzen
    -> BulkAttributeRenamer
DM16NplBE_BielNidau.Nutzungsplanung.WF_FeststellungWald (reader ch.ehi.fme.Main_1)
    attributes: xtf_id xtf_char(200), Verbindlichkeit xtf_char(255), Bemerkung xtf_char(160), Datenverwaltungsstelle xtf_char(200), ZustaendigeStelle xtf_char(200)
    -> AttributeCreator_12
AttributeCreator_12
    ATTR_TABLE = SET_TO Layer = Waldgrenzen
    -> BulkAttributeRenamer_2
    -> Tester_2
DM16NplBE_BielNidau.Nutzungsplanung.WF_FeststellungWaldRV (reader ch.ehi.fme.Main_1)
    attributes: xtf_id xtf_char(200), Typ xtf_char(200), Vorschrift xtf_char(200), ArtikelNr xtf_char(40)
    -> AttributeCreator_13
AttributeCreator_13
    ATTR_TABLE = SET_TO Layer = Waldgrenzen
    -> BulkAttributeRenamer_4

Bookmark: Waldgrenzen.Verbindlichkeit = Festlegung.Kanton
Tester_2
    BOOL_OP = OR
    COMPOSITE_TEST = 1 OR 2
    TEST_CLAUSE:
      TEST @Value(Verbindlichkeit) = Festlegung.Gemeinde
      TEST @Value(Verbindlichkeit) = Festlegung.Region
    TEST_MODE = TEST
    PASSED -> AttributeCreator_25
AttributeCreator_25
    ATTR_TABLE = SET_TO ERROR = Waldgrenzen müssen mit der Verbindlichkeit "Festlegung.Kanton" erfasst werden.
    -> ERROR

Bookmark: NHS
DM16NplBE_BielNidau.Nutzungsplanung.NH_FlaechenelementNHS (reader ch.ehi.fme.Main_1)
    attributes: xtf_id xtf_char(200), Objekt xtf_char(200), Beschrieb xtf_char(160), Genehmigung xtf_date, Inkraftsetzung xtf_date, Qualitaet xtf_char(255)
    -> AttributeCreator_8
DM16NplBE_BielNidau.Nutzungsplanung.NH_LinienelementNHS (reader ch.ehi.fme.Main_1)
    attributes: xtf_id xtf_char(200), Objekt xtf_char(200), Beschrieb xtf_char(160), Genehmigung xtf_date, Inkraftsetzung xtf_date, Qualitaet xtf_char(255)
    -> AttributeCreator_8
DM16NplBE_BielNidau.Nutzungsplanung.NH_PunktelementNHS (reader ch.ehi.fme.Main_1)
    attributes: xtf_id xtf_char(200), Objekt xtf_char(200), Beschrieb xtf_char(160), Genehmigung xtf_date, Inkraftsetzung xtf_date, Qualitaet xtf_char(255), Ori xtf_decimal(5,1)
    -> AttributeCreator_8
AttributeCreator_8
    ATTR_TABLE = SET_TO Layer = NHS
    -> BulkAttributeRenamer
DM16NplBE_BielNidau.Nutzungsplanung.NH_NHSchutz (reader ch.ehi.fme.Main_1)
    attributes: xtf_id xtf_char(200), Verbindlichkeit xtf_char(255), KantArt xtf_char(255), Abkuerzung xtf_char(28), Bezeichnung xtf_char(300), Bedeutung xtf_char(255), Schutzgrad xtf_char(255), Planbeschriftung xtf_char(300), Bemerkung xtf_char(160), DarstellungCode xtf_char(5), Datenverwaltungsstelle xtf_char(200), ZustaendigeStelle xtf_char(200)
    -> AttributeCreator_9
AttributeCreator_9
    ATTR_TABLE = SET_TO Layer = NHS
    -> BulkAttributeRenamer_2
DM16NplBE_BielNidau.Nutzungsplanung.NH_NHSchutzRV (reader ch.ehi.fme.Main_1)
    attributes: xtf_id xtf_char(200), Typ xtf_char(200), Vorschrift xtf_char(200), ArtikelNr xtf_char(40)
    -> AttributeCreator_10
AttributeCreator_10
    ATTR_TABLE = SET_TO Layer = NHS
    -> BulkAttributeRenamer_4

Bookmark: Gewässerraum
DM16NplBE_BielNidau.Nutzungsplanung.GR_Gewaesserraumflaeche (reader ch.ehi.fme.Main_1)
    attributes: xtf_id xtf_char(200), Objekt xtf_char(200), Qualitaet xtf_char(255), Genehmigung xtf_date, Inkraftsetzung xtf_date
    -> AttributeCreator_5
DM16NplBE_BielNidau.Nutzungsplanung.GR_Gewaesserraumlinie (reader ch.ehi.fme.Main_1)
    attributes: xtf_id xtf_char(200), Objekt xtf_char(200), AbstandLinks xtf_decimal(5,2), AbstandRechts xtf_decimal(5,2), AbstandDefinition xtf_char(255), Qualitaet xtf_char(255), Genehmigung xtf_date, Inkraftsetzung xtf_date
    -> AttributeCreator_5
AttributeCreator_5
    ATTR_TABLE = SET_TO Layer = Gewässerraum
    -> BulkAttributeRenamer
DM16NplBE_BielNidau.Nutzungsplanung.GR_GewaesserraumRV (reader ch.ehi.fme.Main_1)
    attributes: xtf_id xtf_char(200), Typ xtf_char(200), Vorschrift xtf_char(200), ArtikelNr xtf_char(40)
    -> AttributeCreator_7
AttributeCreator_7
    ATTR_TABLE = SET_TO Layer = Gewässerraum
    -> BulkAttributeRenamer_4
DM16NplBE_BielNidau.Nutzungsplanung.GR_Gewaesserraum (reader ch.ehi.fme.Main_1)
    attributes: xtf_id xtf_char(200), Verbindlichkeit xtf_char(255), Bemerkung xtf_char(160), Bezeichnung xtf_char(300), DarstellungCode xtf_char(5), Datenverwaltungsstelle xtf_char(200), ZustaendigeStelle xtf_char(200)
    -> AttributeCreator_6
AttributeCreator_6
    ATTR_TABLE = SET_TO Layer = Gewässerraum
    -> BulkAttributeRenamer_2

Bookmark: Bauweise
DM16NplBE_BielNidau.Nutzungsplanung.BN_BW (reader ch.ehi.fme.Main_1)
    attributes: xtf_id xtf_char(200), Verbindlichkeit xtf_char(255), Bauweise xtf_char(150), KantArt xtf_char(255), DarstellungCode xtf_char(5), Beschrieb xtf_char(160), Planbeschriftung xtf_char(300), Datenverwaltungsstelle xtf_char(200), ZustaendigeStelle xtf_char(200), Genehmigung xtf_date, Inkraftsetzung xtf_date, Qualitaet xtf_char(255), Bemerkung xtf_char(160)
    -> AttributeManager_3
AttributeManager_3
    ATTR_TABLE:
      SET_TO GEOM_Layer = Bauweise
      RENAME_SET_VALUE xtf_id > GEOM_xtf_id
      SET_TO TYP_xtf_id = @Value(GEOM_xtf_id)
      RENAME_SET_VALUE Verbindlichkeit > TYP_Verbindlichkeit
      RENAME_SET_VALUE Bauweise > TYP_Bezeichnung
      RENAME_SET_VALUE KantArt > TYP_KantArt
      RENAME_SET_VALUE DarstellungCode > TYP_DarstellungCode
      REMOVE Planbeschriftung
      REMOVE Genehmigung
      REMOVE Inkraftsetzung
      REMOVE ZustaendigeStelle
      REMOVE Beschrieb
      REMOVE Datenverwaltungsstelle
      REMOVE Qualitaet
      REMOVE Bemerkung
    -> FeatureMerger_2 [REQUESTOR]
DM16NplBE_BielNidau.Nutzungsplanung.BN_BWRV (reader ch.ehi.fme.Main_1)
    attributes: xtf_id xtf_char(200), Typ xtf_char(200), Vorschrift xtf_char(200), ArtikelNr xtf_char(40)
    -> BulkAttributeRenamer_4

Bookmark: Grünflächenziffer
DM16NplBE_BielNidau.Nutzungsplanung.BN_GFZ (reader ch.ehi.fme.Main_1)
    attributes: xtf_id xtf_char(200), Verbindlichkeit xtf_char(255), Gruenflaechenziffer xtf_char(150), KantArt xtf_char(255), DarstellungCode xtf_char(5), Beschrieb xtf_char(160), Planbeschriftung xtf_char(300), Datenverwaltungsstelle xtf_char(200), ZustaendigeStelle xtf_char(200), Genehmigung xtf_date, Inkraftsetzung xtf_date, Qualitaet xtf_char(255), Bemerkung xtf_char(160)
    -> AttributeManager_4
AttributeManager_4
    ATTR_TABLE:
      SET_TO GEOM_Layer = Grünflächenziffer
      RENAME_SET_VALUE xtf_id > GEOM_xtf_id
      SET_TO TYP_xtf_id = @Value(GEOM_xtf_id)
      RENAME_SET_VALUE Verbindlichkeit > TYP_Verbindlichkeit
      RENAME_SET_VALUE Gruenflaechenziffer > TYP_Bezeichnung
      RENAME_SET_VALUE KantArt > TYP_KantArt
      RENAME_SET_VALUE DarstellungCode > TYP_DarstellungCode
      REMOVE Beschrieb
      REMOVE Planbeschriftung
      REMOVE Datenverwaltungsstelle
      REMOVE ZustaendigeStelle
      REMOVE Genehmigung
      REMOVE Inkraftsetzung
      REMOVE Qualitaet
      REMOVE Bemerkung
    -> FeatureMerger_2 [REQUESTOR]
DM16NplBE_BielNidau.Nutzungsplanung.BN_GFZRV (reader ch.ehi.fme.Main_1)
    attributes: xtf_id xtf_char(200), Typ xtf_char(200), Vorschrift xtf_char(200), ArtikelNr xtf_char(40)
    -> BulkAttributeRenamer_4

Bookmark: Gebäudelänge / Gebäudetiefe
DM16NplBE_BielNidau.Nutzungsplanung.BN_GL (reader ch.ehi.fme.Main_1)
    attributes: xtf_id xtf_char(200), Verbindlichkeit xtf_char(255), Gebaeudelaengetyp xtf_char(150), Gebaeudelaenge xtf_int32, Gebaeudetiefe xtf_int32, KantArt xtf_char(255), DarstellungCode xtf_char(5), Beschrieb xtf_char(160), Planbeschriftung xtf_char(300), Datenverwaltungsstelle xtf_char(200), ZustaendigeStelle xtf_char(200), Genehmigung xtf_date, Inkraftsetzung xtf_date, Qualitaet xtf_char(255), Bemerkung xtf_char(160)
    -> AttributeManager_5
AttributeManager_5
    ATTR_TABLE:
      SET_TO GEOM_Layer = GebäudelängenGebäudetiefen
      RENAME_SET_VALUE xtf_id > GEOM_xtf_id
      SET_TO TYP_xtf_id = @Value(GEOM_xtf_id)
      RENAME_SET_VALUE Verbindlichkeit > TYP_Verbindlichkeit
      RENAME_SET_VALUE Gebaeudelaengetyp > TYP_Bezeichnung
      RENAME_SET_VALUE KantArt > TYP_KantArt
      RENAME_SET_VALUE DarstellungCode > TYP_DarstellungCode
      REMOVE Gebaeudelaenge
      REMOVE Gebaeudetiefe
      REMOVE Beschrieb
      REMOVE Planbeschriftung
      REMOVE Datenverwaltungsstelle
      REMOVE ZustaendigeStelle
      REMOVE Genehmigung
      REMOVE Inkraftsetzung
      REMOVE Qualitaet
      REMOVE Bemerkung
    -> FeatureMerger_2 [REQUESTOR]
DM16NplBE_BielNidau.Nutzungsplanung.BN_GLRV (reader ch.ehi.fme.Main_1)
    attributes: xtf_id xtf_char(200), Typ xtf_char(200), Vorschrift xtf_char(200), ArtikelNr xtf_char(40)
    -> BulkAttributeRenamer_4

Bookmark: Vorgartenbereiche
DM16NplBE_BielNidau.Nutzungsplanung.BN_VG (reader ch.ehi.fme.Main_1)
    attributes: xtf_id xtf_char(200), Verbindlichkeit xtf_char(255), Vorgartenbereich xtf_char(150), KantArt xtf_char(255), DarstellungCode xtf_char(5), Beschrieb xtf_char(160), Planbeschriftung xtf_char(300), Datenverwaltungsstelle xtf_char(200), ZustaendigeStelle xtf_char(200), Genehmigung xtf_date, Inkraftsetzung xtf_date, Qualitaet xtf_char(255), Bemerkung xtf_char(160)
    -> AttributeManager_6
AttributeManager_6
    ATTR_TABLE:
      SET_TO GEOM_Layer = Vorgartenbereich
      RENAME_SET_VALUE xtf_id > GEOM_xtf_id
      SET_TO TYP_xtf_id = @Value(GEOM_xtf_id)
      RENAME_SET_VALUE Verbindlichkeit > TYP_Verbindlichkeit
      RENAME_SET_VALUE Vorgartenbereich > TYP_Bezeichnung
      RENAME_SET_VALUE KantArt > TYP_KantArt
      RENAME_SET_VALUE DarstellungCode > TYP_DarstellungCode
      REMOVE Beschrieb
      REMOVE Planbeschriftung
      REMOVE Datenverwaltungsstelle
      REMOVE ZustaendigeStelle
      REMOVE Genehmigung
      REMOVE Inkraftsetzung
      REMOVE Qualitaet
      REMOVE Bemerkung
    -> FeatureMerger_2 [REQUESTOR]
DM16NplBE_BielNidau.Nutzungsplanung.BN_VGRV (reader ch.ehi.fme.Main_1)
    attributes: xtf_id xtf_char(200), Typ xtf_char(200), Vorschrift xtf_char(200), ArtikelNr xtf_char(40)
    -> BulkAttributeRenamer_4

Bookmark: Wohnnutzungsanteil
DM16NplBE_BielNidau.Nutzungsplanung.BN_WA (reader ch.ehi.fme.Main_1)
    attributes: xtf_id xtf_char(200), Verbindlichkeit xtf_char(255), Wohnnutzungsanteil xtf_char(150), KantArt xtf_char(255), DarstellungCode xtf_char(5), Beschrieb xtf_char(160), Planbeschriftung xtf_char(300), Datenverwaltungsstelle xtf_char(200), ZustaendigeStelle xtf_char(200), Genehmigung xtf_date, Inkraftsetzung xtf_date, Qualitaet xtf_char(255), Bemerkung xtf_char(160)
    -> AttributeManager_7
AttributeManager_7
    ATTR_TABLE:
      RENAME_SET_VALUE xtf_id > GEOM_xtf_id
      SET_TO GEOM_Layer = Wohnnutzungsanteil
      SET_TO TYP_xtf_id = @Value(GEOM_xtf_id)
      RENAME_SET_VALUE Verbindlichkeit > TYP_Verbindlichkeit
      RENAME_SET_VALUE Wohnnutzungsanteil > TYP_Bezeichnung
      RENAME_SET_VALUE KantArt > TYP_KantArt
      RENAME_SET_VALUE DarstellungCode > TYP_DarstellungCode
      REMOVE Beschrieb
      REMOVE Planbeschriftung
      REMOVE Datenverwaltungsstelle
      REMOVE ZustaendigeStelle
      REMOVE Genehmigung
      REMOVE Inkraftsetzung
      REMOVE Qualitaet
      REMOVE Bemerkung
    -> FeatureMerger_2 [REQUESTOR]
DM16NplBE_BielNidau.Nutzungsplanung.BN_WARV (reader ch.ehi.fme.Main_1)
    attributes: xtf_id xtf_char(200), Typ xtf_char(200), Vorschrift xtf_char(200), ArtikelNr xtf_char(40)
    -> BulkAttributeRenamer_4

Bookmark: Baumstandorte
DM16NplBE_BielNidau.Nutzungsplanung.BN_PktEleBaum (reader ch.ehi.fme.Main_1)
    attributes: xtf_id xtf_char(200), Objekt xtf_char(200), Beschrieb xtf_char(160), Genehmigung xtf_date, Inkraftsetzung xtf_date, Qualitaet xtf_char(255), Ori xtf_decimal(5,1)
    -> AttributeCreator_18
AttributeCreator_18
    ATTR_TABLE = SET_TO Layer = Baumstandorte
    -> BulkAttributeRenamer
DM16NplBE_BielNidau.Nutzungsplanung.BN_Baum (reader ch.ehi.fme.Main_1)
    attributes: xtf_id xtf_char(200), Verbindlichkeit xtf_char(255), Bezeichnung xtf_char(300), Abkuerzung xtf_char(28), KantArt xtf_char(255), DarstellungCode xtf_char(5), Beschrieb xtf_char(160), Planbeschriftung xtf_char(300), Datenverwaltungsstelle xtf_char(200), ZustaendigeStelle xtf_char(200), Bemerkung xtf_char(160)
    -> AttributeCreator_19
AttributeCreator_19
    ATTR_TABLE = SET_TO Layer = Baumstandorte
    -> BulkAttributeRenamer_2
DM16NplBE_BielNidau.Nutzungsplanung.BN_BaumRV (reader ch.ehi.fme.Main_1)
    attributes: xtf_id xtf_char(200), Typ xtf_char(200), Vorschrift xtf_char(200), ArtikelNr xtf_char(40)
    -> AttributeCreator_20
AttributeCreator_20
    ATTR_TABLE = SET_TO Layer = Baumstandorte
    -> BulkAttributeRenamer_4

Bookmark: Geometrie, Typ und Dokumente zusammenführen
Note: GEOM_
BulkAttributeRenamer
    ATTRCHOICE = All Attributes
    MODE_CHOICE = RENAME
    PATTERN_ACTION_DISP = ADDPREFIX
    REPLACE_STR = GEOM_
    -> FeatureMerger_4 [REQUESTOR]
Note: RV_
BulkAttributeRenamer_4
    ATTRCHOICE = All Attributes
    MODE_CHOICE = RENAME
    PATTERN_ACTION_DISP = ADDPREFIX
    REPLACE_STR = RV_
    -> FeatureMerger_3 [REQUESTOR]
Note: TYP_
BulkAttributeRenamer_2
    ATTRCHOICE = All Attributes
    MODE_CHOICE = RENAME
    PATTERN_ACTION_DISP = ADDPREFIX
    REPLACE_STR = TYP_
    -> FeatureMerger_4 [SUPPLIER]
Note: Typ anhängen
FeatureMerger_4
    ATTR_ACCUM_MODE = Merge Supplier
    ATTR_CONFLICT_RES = Use Requestor
    IGNORE_NULLS = No
    JOIN_KEYS = @Value(GEOM_Objekt) @Value(TYP_xtf_id) AUTO @Value(GEOM_Layer) @Value(TYP_Layer) AUTO
    MERGE_TYPE = Attributes Only
    PROCESS_DUPS = NO
    REJECT_NULL_MISSING_KEYS = No
    SUPPLIERS_FIRST = No
    MERGED -> FeatureMerger_2 [REQUESTOR]
DM16NplBE_BielNidau.Nutzungsplanung.Dokument (reader ch.ehi.fme.Main_1)
    attributes: xtf_id xtf_char(200), Art_Doku xtf_char(255), Titel xtf_char(400), OffiziellerTitel xtf_char(400), Abkuerzung xtf_char(40), OffizielleNr xtf_char(40), Gemeinde xtf_int32, Dokument xtf_char(200), ZustaendigeStelle xtf_char(200)
    -> BulkAttributeRenamer_3
Note: DOK_
BulkAttributeRenamer_3
    ATTRCHOICE = All Attributes
    MODE_CHOICE = RENAME
    PATTERN_ACTION_DISP = ADDPREFIX
    REPLACE_STR = DOK_
    -> FeatureMerger_3 [SUPPLIER]
Note: Dok anhängen
FeatureMerger_3
    ATTR_ACCUM_MODE = Merge Supplier
    ATTR_CONFLICT_RES = Use Requestor
    IGNORE_NULLS = No
    JOIN_KEYS = @Value(RV_Vorschrift) @Value(DOK_xtf_id) AUTO
    MERGE_TYPE = Attributes Only
    PROCESS_DUPS = NO
    REJECT_NULL_MISSING_KEYS = No
    SUPPLIERS_FIRST = No
    MERGED -> FeatureMerger_2 [SUPPLIER]
Note: RV anhängen
FeatureMerger_2
    ATTR_ACCUM_MODE = Merge Supplier
    ATTR_CONFLICT_RES = Use Requestor
    IGNORE_NULLS = No
    JOIN_KEYS = @Value(TYP_xtf_id) @Value(RV_Typ) AUTO @Value(TYP_Layer) @Value(RV_Layer) AUTO
    LIST_NAME = Dokumente
    MERGE_TYPE = Attributes Only
    PROCESS_DUPS = NO
    REJECT_NULL_MISSING_KEYS = No
    SUPPLIERS_FIRST = No
    MERGED -> AttributeManager_8
    UNMERGED_REQUESTOR -> AttributeManager_8
Note: Alle Objekte
AttributeManager_8
    ATTR_TABLE:
      REMOVE TYP_Beschrieb
      REMOVE GEOM_Objekt
      REMOVE GEOM_Genehmigung
      REMOVE GEOM_Inkraftsetzung
      REMOVE GEOM_Qualitaet
      REMOVE GEOM_Beschrieb
      REMOVE GEOM_Ori
      REMOVE GEOM_AbstandLinks
      REMOVE GEOM_AbstandRechts
      REMOVE GEOM_AbstandDefinition
      REMOVE TYP_Layer
      REMOVE TYP_Planbeschriftung
      REMOVE TYP_Datenverwaltungsstelle
      REMOVE TYP_ZustaendigeStelle
      REMOVE TYP_Bemerkung
      REMOVE TYP_Art
      REMOVE TYP_BeschrVorsprGebTeile
      REMOVE TYP_Nutzungsziffer
      REMOVE TYP_Nutzungsziffer_Art
      REMOVE TYP_Gruenflaechenziffer
      REMOVE TYP_Bedeutung
      REMOVE TYP_Schutzgrad
      REMOVE GEOM_ZonentypRef
      REMOVE GEOM_Laermempfindlichkeit
      REMOVE GEOM_Planbeschriftung
      REMOVE GEOM_Bemerkung
      REMOVE GEOM_Flaechenmass
      REMOVE GEOM_Verkehrsraumart
      REMOVE TYP_BR_Nutzungsart
      REMOVE TYP_BR_Nutzungsmass
      REMOVE RV_xtf_id
      REMOVE RV_Typ
      REMOVE RV_Vorschrift
      REMOVE RV_ArtikelNr
      REMOVE RV_Layer
      REMOVE DOK_xtf_id
      REMOVE DOK_Art_Doku
      REMOVE DOK_Titel
      REMOVE DOK_OffiziellerTitel
      REMOVE DOK_Abkuerzung
      REMOVE DOK_OffizielleNr
      REMOVE DOK_Gemeinde
      REMOVE DOK_Dokument
      REMOVE DOK_ZustaendigeStelle
      REMOVE Dokumente{}.RV_xtf_id
      REMOVE Dokumente{}.RV_Typ
      REMOVE Dokumente{}.RV_Vorschrift
      REMOVE Dokumente{}.RV_ArtikelNr
      REMOVE Dokumente{}.RV_Layer
      REMOVE Dokumente{}.DOK_Gemeinde
      REMOVE Dokumente{}.DOK_ZustaendigeStelle
    -> TestFilter
    -> TestFilter_2

Bookmark: Jede Festlegung muss mit mind. 1 Rechtsvorschrift verlinkt sein
Note: Nur Festlegungen
TestFilter
    DEFAULT_VALUE = Festlegung
    TEST_LIST = "BOOL_OP,OR,COMPOSITE_TEST,""""""1"""""",TEST_CLAUSE,TEST @Value(TYP_Verbindlichkeit) = Hinweis",Hinweis
    Festlegung -> ListSearcher
Note: Prüfen, ob in der Liste Dokumente{} mind. 1 Objekt mit Art_Doku = Rechtsvorschrift gefunden wird.
ListSearcher
    ATTR_VALUE = Rechtsvorschrift
    INDEX_ATTR = _list_index
    LIST_ATTR = Dokumente{}.DOK_Art_Doku
    MATCHTYPE = FIRST_MATCHED_ENCODED
    NOT_FOUND -> AttributeKeeper
AttributeKeeper
    CREATE_BULK_MODE_FEATURES = NO
    KEEP_ATTRS = GEOM_Layer,GEOM_xtf_id,TYP_Bezeichnung,TYP_xtf_id,TYP_Abkuerzung,TYP_DarstellungCode,TYP_KantArt,TYP_Verbindlichkeit
    -> DuplicateFilter
Note: Typ ohne verlinkte Rechtsvorschrift nur einmal aufführen.
DuplicateFilter
    INPUT_ORDERED_CHOICE = No
    KEYATTR = TYP_xtf_id
    UNIQUE -> AttributeCreator_2
AttributeCreator_2
    ATTR_TABLE = SET_TO ERROR = Jede Festlegung muss mit mind. 1 Rechtsvorschrift verlinkt sein.
    -> ERROR

Bookmark: Innere Nutzung und SV-Perimeter in der Nutzungszone müssen deckungsgleich sein
Note: Nur SV-Perimeter aus NZ
TestFilter_2
    DEFAULT_VALUE = <UNFILTERED>
    TEST_LIST:
      "BOOL_OP,AND,COMPOSITE_TEST,""""""1 AND 2 AND 3"""""",TEST_CLAUSE,TEST @Value(TYP_KantArt) IN UEO,ZPP,USP,SBV
      TEST @Value(GEOM_Layer) = NZ
      TEST @Value(TYP_BN_SV_DarstellungInNZPlan) = ja",SV-Perimeter
    SV-Perimeter -> AttributeRemover
AttributeRemover
    LIST_ATTRS = Dokumente{}.DOK_Abkuerzung Dokumente{}.DOK_Art_Doku Dokumente{}.DOK_Dokument Dokumente{}.DOK_OffizielleNr Dokumente{}.DOK_OffiziellerTitel Dokumente{}.DOK_Titel Dokumente{}.DOK_xtf_id
    -> AreaOnAreaOverlayer [AREA]
DM16NplBE_BielNidau.Nutzungsplanung.GN_Grundzone_ZPP_UeO (reader ch.ehi.fme.Main_1)
    attributes: xtf_id xtf_char(200), KantArt xtf_char(255), Genehmigung xtf_date, Inkraftsetzung xtf_date, Laermempfindlichkeit xtf_char(255), Beschrieb xtf_char(160), Planbeschriftung xtf_char(300), Qualitaet xtf_char(255), Bemerkung xtf_char(160), Flaechenmass xtf_int32
    -> AttributeFilter
    -> AttributeManager_9
AttributeManager_9
    ATTR_TABLE:
      SET_TO GEOM_Layer = Innere Nutzung
      RENAME_SET_VALUE xtf_id > GEOM_xtf_id
      RENAME_SET_VALUE KantArt > Typ_KantArt
      REMOVE Genehmigung
      REMOVE Inkraftsetzung
      REMOVE Laermempfindlichkeit
      REMOVE Beschrieb
      REMOVE Planbeschriftung
      REMOVE Qualitaet
      REMOVE Bemerkung
      REMOVE Flaechenmass
    -> AreaOnAreaOverlayer [AREA]
Note: Verschnitt SV-Perimeter / und innere Nutzung
AreaOnAreaOverlayer
    ACCUM_ATTRS_NAME = Use Attributes From One Feature
    CLEANING_TOLERANCE = Automatic
    CONNECT_Z_MODE = First Wins
    DEAGGREGATE_INPUT = Yes
    OVC_ATTR = _overlaps
    AREA -> AreaCalculator
Note: Fläche berechnen
AreaCalculator
    AREA_ATTR = _area
    AREA_TYPE = Plane Area
    MULT = 1
    -> Tester
Note: Nur Flächen, ohne Überlappung / und grösser als Toleranz
Tester
    BOOL_OP = COMPOSITE
    COMPOSITE_TEST = 1 AND 2
    TEST_CLAUSE:
      TEST @Value(_overlaps) = 1
      TEST @Value(_area) >= 0.05
    TEST_MODE = TEST
    PASSED -> AttributeCreator_4
AttributeCreator_4
    ATTR_TABLE = SET_TO ERROR = SV-Perimeter aus NZ und innere Nutzung müssen deckungsgleich sein.
    -> ERROR

Bookmark: HinweisWeitereDokumente: Ursprung und Hinweis dürfen nicht identisch sein
DM16NplBE_BielNidau.Nutzungsplanung.HinweisWeitereDokumente (reader ch.ehi.fme.Main_1)
    attributes: xtf_id xtf_char(200), Ursprung xtf_char(200), Hinweis xtf_char(200), ArtikelNr xtf_char(40), Ordnungsnummer xtf_int32
    -> Tester_3
Tester_3
    BOOL_OP = OR
    COMPOSITE_TEST = 1
    TEST_CLAUSE = TEST @Value(Ursprung) = @Value(Hinweis)
    TEST_MODE = TEST
    PASSED -> AttributeCreator_26
AttributeCreator_26
    ATTR_TABLE = SET_TO ERROR = Die Attribute "Ursprung" und "Hinweis" dürfen nicht identisch sein.
    -> ERROR

Bookmark: Kantart der inneren Nutzung darf nicht UEO, ZPP, USP oder SBV sein
AttributeFilter
    ATTR_NAME = KantArt
    ATTR_VALUES = UEO,ZPP,SBV,USP,<Empty>,<Missing>,<Null>,<Unfiltered>
    UEO -> AttributeKeeper_2
    ZPP -> AttributeKeeper_2
    SBV -> AttributeKeeper_2
    USP -> AttributeKeeper_2
AttributeKeeper_2
    CREATE_BULK_MODE_FEATURES = NO
    KEEP_ATTRS = KantArt,xtf_id
    -> AttributeCreator
AttributeCreator
    ATTR_TABLE = SET_TO ERROR = Die innere Nutzung darf keine der folgenden KantArts aufweisen: UEO, ZPP, USP, SBV.
    -> ERROR
